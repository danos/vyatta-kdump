module vyatta-op-crash-dump-v1 {
	namespace "urn:vyatta.com:mgmt:vyatta-op-rash-dump:1";
	prefix vyatta-op-crash-dump-v1;

	import vyatta-opd-extensions-v1 {
		prefix opd;
	}
	import vyatta-op-show-v1 {
		prefix show;
	}
	import vyatta-op-show-system-v1 {
		prefix show-sys;
	}
	import vyatta-op-delete-v1 {
		prefix delete;
	}
	import vyatta-op-delete-system-v1 {
		prefix delete-sys;
	}

	organization "AT&T Inc.";
	contact
		"AT&T
		 Postal: 208 S. Akard Street
				 Dallas, TX 75202
		 Web: www.att.com";

	description
		"Copyright (c) 2021, AT&T Intellectual Property.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Defines op mode comamnds for kernel crash dump.";

	revision 2021-07-10 {
		description "Initial version.";
	}

	opd:augment /show:show/show-sys:system {
		opd:command  kernel-crash-dump {
			opd:help "Show kernel crash-dump status and a list of saved kernel crash-dumps";
			opd:on-enter '/lib/vci-kdump/kdump-op --show';

			opd:argument index {
				type int32;
				opd:allowed '/lib/vci-kdump/kdump-op --allowed';
				opd:help "Crash dump index";

				opd:command messages {
					opd:help "Show messages";
					opd:on-enter '/lib/vci-kdump/kdump-op --message -- $4';
				}
			}
		}
	}

	opd:augment /delete:delete/delete-sys:system {
		opd:command kernel-crash-dump {
			opd:help "Delete kernel crash dumps";
			opd:on-enter '/lib/vci-kdump/kdump-op -delete';

			opd:argument index {
				type int32;
				opd:allowed '/lib/vci-kdump/kdump-op -allowed';
				opd:help "Crash dump index to delete";
				opd:on-enter '/lib/vci-kdump/kdump-op -delete -- $4';
			}
		}
	}
}
